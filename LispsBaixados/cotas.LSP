(defun c:carregaconfigcotas()
   (cota_cortes)
   (cota_plantabaixa)
)

(defun cota_plantabaixa ()
  (setvar "cmdecho" 0)
  (command "DIM" "SAVE" "Planta Baixa" "Y" "exit")
  (command "-dimstyle" "AN" "Y" "Planta Baixa" "y" "A" "")(command "-dimstyle" "R" "all")
  (command "DIMALT" "0")
  (command "DIMALTF" "0.04")
  (command "DIMALTTD" "3")
  (command "DIMALTTZ" "0")
  (command "DIMALTU" "2")
  (command "DIMALTZ" "0")
  (command "DIMAPOST" "")
  (command "DIMARCSYM" "0")
  (command "DIMASO" "1")
  (command "DIMASSOC" "2")
  (command "DIMASZ" "0.1500")
  (command "DIMATFIT" "3")
  (command "DIMAUNIT" "1")
  (command "DIMBLK" "Oblique")
  (command "DIMBLK1" "")
  (command "DIMBLK2" "")
  (command "DIMCEN" "0.1500")
  (command "DIMCLRD" "250")
  (command "DIMCLRE" "250")
  (command "DIMCLRT" "250")
  (command "DIMDEC" "2")
  (command "DIMDLE" "0.1500")
  (command "DIMDLI" "0.1500")
  (command "DIMDSEP" ",")
  (command "DIMEXE" "0.1500")
  (command "DIMEXO" "0.1500")
  (command "DIMFIT" "3")
  (command "DIMFRAC" "0")
  (command "DIMFXL" "0.1500")
  (command "DIMFXLON" "0")
  (command "DIMGAP" "0.0500")
  (command "DIMJOGANG" "90")
  (command "DIMJUST" "0")
  (command "DIMLAYER" ".")
  (command "DIMLDRBLK" "Oblique")
  (command "DIMLFAC" "1.0000")
  (command "DIMLIM" "0")
  (command "DIMLTEX1" "")
  (command "DIMLTEX2" "")
  (command "DIMLTYPE" "")
  (command "DIMLUNIT" "2")
  (command "DIMLWD" "-2")
  (command "DIMLWE" "-2")
  (command "DIMPICKBOX" "5")
  (command "DIMPOST" "")
  (command "DIMRND" "0.0000")
  (command "DIMSAH" "0")
  (command "DIMSD1" "1")
  (command "DIMSD2" "1")
  (command "DIMSE1" "1")
  (command "DIMSE2" "1")
  (command "DIMSHO" "1")
  (command "DIMSOXD" "0")
  (command "DIMTAD" "0")
  (command "DIMTDEC" "2")
  (command "DIMTFAC" "1.0000")
  (command "DIMTFILL" "0")
  (command "DIMTFILLCLR" "0")
  (command "DIMTIH" "0")
  (command "DIMTIX" "0")
  (command "DIMTM" "0.0000")
  (command "DIMTMOVE" "0")
  (command "DIMTOFL" "1")
  (command "DIMTOH" "0")
  (command "DIMTOL" "0")
  (command "DIMTOLJ" "0")
  (command "DIMTP" "0.0000")
  (command "DIMTSZ" "0.0000")
  (command "DIMTVP" "0.0000")
  (command "DIMTXT" "0.12")
  (command "DIMTXTDIRECTION" "0")
  (command "DIMTXTRULER" "1")
  (command "DIMTZIN" "8")
  (command "DIMUNIT" "2")
  (command "DIMUPT" "1")
  (command "DIMZIN" "1")
  (command "style" "Standard" "Arial" "A" "" "" "" "" "" "" "" ""); CONFIGURA O ESTLO DE TEXTO STANDARD EM ANNOTATIVO
  (command "DIMTXSTY" "Standard")
  (command "zoom" "e")
  (command "-dimstyle" "s" "Planta Baixa" "y")
  (command "dim" "UP" "ALL" "" "EXIT")
  (princ)
  (Prompt "OS ESTILOS DE COTAS DE ARQUITETURA FORAM CONFIGURADOS COM SUCESSO.")
  (setvar "cmdecho" 1)
  (princ)
)

(defun cota_cortes ()
  (setvar "cmdecho" 0)
  (command "DIM" "SAVE" "Cortes" "Y" "exit")
  (command "-dimstyle" "AN" "Y" "Cortes" "y" "A" "")(command "-dimstyle" "R" "all")
  (command "DIMALT" "0")
  (command "DIMALTF" "0.04")
  (command "DIMALTTD" "3")
  (command "DIMALTTZ" "0")
  (command "DIMALTU" "2")
  (command "DIMALTZ" "0")
  (command "DIMAPOST" "")
  (command "DIMARCSYM" "0")
  (command "DIMASO" "1")
  (command "DIMASSOC" "2")
  (command "DIMASZ" "0.1500")
  (command "DIMATFIT" "3")
  (command "DIMAUNIT" "1")
  (command "DIMBLK" "Oblique")
  (command "DIMBLK1" "")
  (command "DIMBLK2" "")
  (command "DIMCEN" "0.1500")
  (command "DIMCLRD" "250")
  (command "DIMCLRE" "250")
  (command "DIMCLRT" "250")
  (command "DIMDEC" "2")
  (command "DIMDLE" "0.1500")
  (command "DIMDLI" "0.1500")
  (command "DIMDSEP" ",")
  (command "DIMEXE" "0.1500")
  (command "DIMEXO" "0.1500")
  (command "DIMFIT" "3")
  (command "DIMFRAC" "0")
  (command "DIMFXL" "0.1500")
  (command "DIMFXLON" "0")
  (command "DIMGAP" "0.0500")
  (command "DIMJOGANG" "90")
  (command "DIMJUST" "0")
  (command "DIMLAYER" ".")
  (command "DIMLDRBLK" "Oblique")
  (command "DIMLFAC" "1.0000")
  (command "DIMLIM" "0")
  (command "DIMLTEX1" "")
  (command "DIMLTEX2" "")
  (command "DIMLTYPE" "")
  (command "DIMLUNIT" "2")
  (command "DIMLWD" "-2")
  (command "DIMLWE" "-2")
  (command "DIMPICKBOX" "5")
  (command "DIMPOST" "")
  (command "DIMRND" "0.0000")
  (command "DIMSAH" "0")
  (command "DIMSD1" "0") ;linhas da cota
  (command "DIMSD2" "0") ;linhas da cota
  (command "DIMSE1" "0") ;linhas da cota
  (command "DIMSE2" "0") ;linhas da cota
  (command "DIMSHO" "1")
  (command "DIMSOXD" "0")
  (command "DIMTAD" "0")
  (command "DIMTDEC" "2")
  (command "DIMTFAC" "1.0000")
  (command "DIMTFILL" "0")
  (command "DIMTFILLCLR" "0")
  (command "DIMTIH" "0")
  (command "DIMTIX" "0")
  (command "DIMTM" "0.0000")
  (command "DIMTMOVE" "0")
  (command "DIMTOFL" "1")
  (command "DIMTOH" "0")
  (command "DIMTOL" "0")
  (command "DIMTOLJ" "0")
  (command "DIMTP" "0.0000")
  (command "DIMTSZ" "0.0000")
  (command "DIMTVP" "0.0000")
  (command "DIMTXT" "0.12")
  (command "DIMTXTDIRECTION" "0")
  (command "DIMTXTRULER" "1")
  (command "DIMTZIN" "8")
  (command "DIMUNIT" "2")
  (command "DIMUPT" "1")
  (command "DIMZIN" "1")
  (command "style" "Standard" "Arial" "A" "" "" "" "" "" "" "" ""); CONFIGURA O ESTLO DE TEXTO STANDARD EM ANNOTATIVO
  (command "DIMTXSTY" "Standard")
  (command "zoom" "e")
  (command "-dimstyle" "s" "Cortes" "y")
  (command "dim" "UP" "ALL" "" "EXIT")
  (princ)
  (Prompt "OS ESTILOS DE COTAS DE CORTES FORAM CONFIGURADOS COM SUCESSO.")
  (setvar "cmdecho" 1)
  (princ)
)
